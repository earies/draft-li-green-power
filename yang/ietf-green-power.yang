module ietf-green-power {
  yang-version 1.1;
  namespace "urn:ietf:params:xml:ns:yang:ietf-green-power";
  prefix gp;

  import ietf-hardware {
    prefix hw;
    reference
      "RFC 8348: A YANG Data Model for Hardware Management";
  }

  organization
    "IETF GREEN (Getting Ready for Energy-Efficient Networking) Working
     Group";

  contact
    "WG Web: <https://datatracker.ietf.org/wg/green/
     WG List: <mailto:green@ietf.org>
     Editor: Tony Li
             <mailto:tony.li@tony.li>
     Editor: Ron Bonica
             <mailto:rbonica@juniper.net>
     Editor: Ebben Aries
             <mailto:exa@juniper.net>";

  description
    "This document defines a YANG data model that can be used to manage
     and monitor power related attributes of hardware components.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC 9249; see the
     RFC itself for full legal notices.";

  revision 2024-11-19 {
    description
      "Initial version";
    reference
      "RFC XXXX: A YANG Data Model for Power Management";
  }

  grouping power-attributes {
    description
      "";

    leaf used-power {
      type uint32;
      config false;
      units milliwatts;
      description
        "";
    }

    leaf power-save-capable {
      type boolean;
      config false;
      description
        "";
    }

    leaf power-save {
      type boolean;
      description
        "";
    }

    leaf-list required-components {
      type leafref {
        path "../../../hw:component/hw:name";
      }
      config false;
      description
        "";
    }

    leaf-list dependent-components {
      type leafref {
        path "../../../hw:component/hw:name";
      }
      config false;
      description
        "";
    }
  }

  grouping power-top {
    description
      "";

    container power {
      description
        "";

      uses power-attributes;
    }
  }

  augment "/hw:hardware/hw:component" {
    uses power-top;
  }
}
